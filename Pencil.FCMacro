import FreeCAD, Part, Draft

# Ensure there is an active document
if FreeCAD.ActiveDocument is None:
    FreeCAD.newDocument()

# Parameters
body_length = 150  # Length of the pencil body
body_radius = 3.5  # Radius of the pencil body
tip_length = 20    # Length of the colored tip
eraser_length = 10 # Length of the eraser
eraser_radius = 4  # Radius of the eraser
color_body = (1.0, 0.65, 0.0)  # RGB color for the body
color_tip = (0.0, 0.0, 0.0)    # RGB color for the tip
color_eraser = (1.0, 0.3, 0.3) # RGB color for the eraser

# Create pencil body
body = Part.makeCylinder(body_radius, body_length)
body_obj = FreeCAD.ActiveDocument.addObject("Part::Feature", "PencilBody")
body_obj.Shape = body

# Create pencil tip
tip = Part.makeCone(body_radius, 0, tip_length)
tip_placement = FreeCAD.Placement(FreeCAD.Vector(0, 0, body_length), FreeCAD.Rotation(0, 0, 0, 1))
tip.Placement = tip_placement
tip_obj = FreeCAD.ActiveDocument.addObject("Part::Feature", "PencilTip")
tip_obj.Shape = tip

# Create eraser
eraser = Part.makeCylinder(eraser_radius, eraser_length)
eraser_placement = FreeCAD.Placement(FreeCAD.Vector(0, 0, -eraser_length), FreeCAD.Rotation(0, 0, 0, 1))
eraser.Placement = eraser_placement
eraser_obj = FreeCAD.ActiveDocument.addObject("Part::Feature", "PencilEraser")
eraser_obj.Shape = eraser

# Set colors
Gui.ActiveDocument.getObject(body_obj.Name).ShapeColor = color_body
Gui.ActiveDocument.getObject(tip_obj.Name).ShapeColor = color_tip
Gui.ActiveDocument.getObject(eraser_obj.Name).ShapeColor = color_eraser

FreeCAD.ActiveDocument.recompute()
