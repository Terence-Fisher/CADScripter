import FreeCAD as App
import Part, math

def createOCCBottle(myWidth=50.0, myHeight=70.0, myThickness=30.0):
    aPnt1 = App.Vector(-myWidth / 2., 0, 0)
    aPnt2 = App.Vector(-myWidth / 2., -myThickness / 4., 0)
    aPnt3 = App.Vector(0, -myThickness / 2., 0)
    aPnt4 = App.Vector(myWidth / 2., -myThickness / 4., 0)
    aPnt5 = App.Vector(myWidth / 2., 0, 0)

    aArcOfCircle = Part.Arc(aPnt2, aPnt3, aPnt4)
    aSegment1 = Part.LineSegment(aPnt1, aPnt2)
    aSegment2 = Part.LineSegment(aPnt4, aPnt5)

    aEdge1 = aSegment1.toShape()
    aEdge2 = aArcOfCircle.toShape()
    aEdge3 = aSegment2.toShape()
    aWire = Part.Wire([aEdge1, aEdge2, aEdge3])

    aTrsf = App.Matrix()
    aTrsf.rotateZ(math.pi)  # rotate around the z-axis

    aMirroredWire = aWire.copy()
    aMirroredWire.transformShape(aTrsf)
    myWireProfile = Part.Wire([aWire, aMirroredWire])

    myFaceProfile = Part.Face(myWireProfile)
    aPrismVec = App.Vector(0, 0, myHeight)
    myBody = myFaceProfile.extrude(aPrismVec)

    myBody = myBody.makeFillet(myThickness / 12.0, myBody.Edges)

    neckLocation = App.Vector(0, 0, myHeight)
    neckNormal = App.Vector(0, 0, 1)

    myNeckRadius = myThickness / 4.
    myNeckHeight = myHeight / 10.
    myNeck = Part.makeCylinder(myNeckRadius, myNeckHeight, neckLocation, neckNormal)
    myBody = myBody.fuse(myNeck)

    return myBody

# Create the OCC bottle part
occ_bottle = createOCCBottle()

# Create a document in FreeCAD
doc = App.newDocument()

# Add the OCC bottle part to the document
occ_bottle_object = doc.addObject("Part::Feature", "OCC_bottle")
occ_bottle_object.Shape = occ_bottle

# Show the object in the FreeCAD interface
doc.recompute()

print("OCC bottle part 'OCC_bottle' created successfully.")
